module hack-impl {
    yang-version 1;
    namespace "urn:opendaylight:params:xml:ns:yang:hack:impl";
    prefix "hack-impl";

    import config { prefix config; revision-date 2013-04-05; }
    import opendaylight-md-sal-binding { prefix md-sal-binding; revision-date 2013-10-28;}

    description
        "Service definition for hack project";

    revision "2014-12-10" {
        description
            "Initial revision";
    }

    identity hack {
        base config:module-type;
        config:java-name-prefix Hack;
    }

    augment "/config:modules/config:module/config:configuration" {
        case hack {
            when "/config:modules/config:module/config:type = 'hack'";
            container broker {
                uses config:service-ref {
                    refine type {
                        mandatory true;
                        config:required-identity md-sal-binding:binding-broker-osgi-registry;
                    }
                }
            }
        }
    }
}
