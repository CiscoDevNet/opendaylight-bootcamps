module caching-mountpoint-impl {
    yang-version 1;
    namespace "urn:opendaylight:params:xml:ns:yang:caching-mountpoint:impl";
    prefix "caching-mountpoint-impl";

    import config { prefix config; revision-date 2013-04-05; }
    import opendaylight-md-sal-binding { prefix md-sal-binding; revision-date 2013-10-28;}
    import opendaylight-md-sal-dom {prefix dom;}


    description
        "Service definition for caching-mountpoint project";

    revision "2014-12-10" {
        description
            "Initial revision";
    }

    identity caching-mountpoint {
        base config:module-type;
        config:java-name-prefix CachingMountpoint;
    }

    augment "/config:modules/config:module/config:configuration" {
        case caching-mountpoint {
            when "/config:modules/config:module/config:type = 'caching-mountpoint'";

             container dom-broker {
                uses config:service-ref {
                    refine type {
                        mandatory true;
                        config:required-identity dom:dom-broker-osgi-registry;
                    }
                }
            }
        }
    }
}
