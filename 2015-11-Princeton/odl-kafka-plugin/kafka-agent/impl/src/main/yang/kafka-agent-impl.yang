module kafka-agent-impl {
    yang-version 1;
    namespace "urn:opendaylight:params:xml:ns:yang:kafka-agent:impl";
    prefix "kafka-agent-impl";

    import config { prefix config; revision-date 2013-04-05; }
    import opendaylight-md-sal-binding { prefix md-sal-binding; revision-date 2013-10-28;}
    import opendaylight-md-sal-dom { prefix md-sal-dom; revision-date 2013-10-28;}

    description
        "Service definition for kafka-agent project";

    revision "2015-09-22" {
        description
            "Initial revision";
    }

    identity kafka-agent {
        base config:module-type;
        config:java-name-prefix Kafka;
    }

    augment "/config:modules/config:module/config:configuration" {
        case kafka-agent {
            when "/config:modules/config:module/config:type = 'kafka-agent'";
            container binding-broker {
                uses config:service-ref {
                    refine type {
                        mandatory true;
                        config:required-identity md-sal-binding:binding-broker-osgi-registry;
                    }
                }
            }
            container dom-broker {
                uses config:service-ref {
                    refine type {
                        mandatory true;
                        config:required-identity md-sal-dom:dom-broker-osgi-registry;
                     }
                }
             }
        }
    }
}
