module caching-mountpoint {
    yang-version 1;
    namespace "urn:opendaylight:params:xml:ns:yang:caching-mountpoint";
    prefix "caching-mountpoint";

    revision "2015-01-05" {
        description "Initial revision of caching-mountpoint model";
    }
}
